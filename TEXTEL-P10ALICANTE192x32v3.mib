-- ***************************************************************************
-- *
-- * Copyright (c) 2019 Textel Marimon s.a. Inc. All Rights Reserved.
-- *
-- * Module Name:  TEXTEL-P10ALICANTE192x32v3
-- *
-- * Description:  DEFINE OBJETOS PARA MANEJAR TELEINDICADORES  
-- * 
-- ***************************************************************************

TEXTEL-P10ALICANTE192x32v3 DEFINITIONS ::= BEGIN


	IMPORTS
	NOTIFICATION-TYPE, OBJECT-TYPE, MODULE-IDENTITY, 
	enterprises, Integer32
		FROM SNMPv2-SMI
	NOTIFICATION-GROUP, OBJECT-GROUP, MODULE-COMPLIANCE
		FROM SNMPv2-CONF
	RowStatus, DisplayString
		FROM SNMPv2-TC;


textel-Marimon 	OBJECT IDENTIFIER ::= { enterprises 46536 }


	nombreCompleto OBJECT-TYPE
	SYNTAX OCTET STRING
	ACCESS read-only
	STATUS current
	DESCRIPTION
		"Nombre del fabricante del display."
	::= { textel-Marimon 1 }


display OBJECT IDENTIFIER ::= { textel-Marimon 2 }

		
	numeroSerie OBJECT-TYPE
		SYNTAX OCTET STRING
		ACCESS read-only
		STATUS current
		DESCRIPTION
			"Nœmero de serie del fabricante"
		::= { display 1 }

	identificador OBJECT-TYPE
		SYNTAX OCTET STRING
		ACCESS read-only
		STATUS current
		DESCRIPTION
			"identificador del teleindicador."
		::= { display 2 }

	direccion OBJECT-TYPE
		SYNTAX OCTET STRING
		ACCESS read-only
		STATUS current
		DESCRIPTION
			"calle y numero."
		::= { display 3 }

	displayGeneralStatus OBJECT-TYPE
		SYNTAX OCTET STRING
		ACCESS read-only
		STATUS current
		DESCRIPTION
			"Estado general del teleindicador (Ok / Error)."
		::= { display 4 }


	master OBJECT IDENTIFIER ::= { display 5 }  
	
		masterErrores OBJECT IDENTIFIER ::= { master 1 }
	
			masterUsbTarjetaErrores OBJECT-TYPE
				SYNTAX OCTET STRING
				ACCESS read-only
				STATUS current
				DESCRIPTION
					"Estado USB tarjeta errores (Ok / Error)."
				::= { masterErrores 1 }

			masterDisplayEncendido OBJECT-TYPE
				SYNTAX Integer32
				ACCESS read-write
				STATUS current
				DESCRIPTION
					"Encendido (0 = OFF / 1 = ON)."
				::= { masterErrores 2 }
	
			masterPuerta OBJECT-TYPE
				SYNTAX OCTET STRING
				ACCESS read-only
				STATUS current
				DESCRIPTION
					"Estado puerta (Abierta / Cerrada)."
				::= { masterErrores 3 }
	
			masterTemperaturaInterior OBJECT-TYPE
				SYNTAX Integer32
				ACCESS read-only
				STATUS current
				DESCRIPTION
					"Temperatura interior (°C)."
				::= { masterErrores 4 }
	
			masterTermostato OBJECT-TYPE
				SYNTAX Integer32
				ACCESS read-write
				STATUS current
				DESCRIPTION
					"Estado termostato (0 = OFF / 1 = ON)."
				::= { masterErrores 5 }
	
			masterVentilador1 OBJECT-TYPE
				SYNTAX OCTET STRING
				ACCESS read-only
				STATUS current
				DESCRIPTION
					"Estado del ventilador 1 (Ok / Error)."
				::= { masterErrores 6 }
	
			masterVentilador2 OBJECT-TYPE
				SYNTAX OCTET STRING
				ACCESS read-only
				STATUS current
				DESCRIPTION
					"Estado del ventilador 2 (Ok / Error)."
				::= { masterErrores 7 }
	
			masterNivelFotocelula OBJECT-TYPE
				SYNTAX Integer32
				ACCESS read-only
				STATUS current
				DESCRIPTION
					"Nivel fotocelula (1 - 100 / 0 = error)."
				::= { masterErrores 8 }     
			
			masterLeds OBJECT-TYPE
				SYNTAX Integer32
				ACCESS read-only
				STATUS current
				DESCRIPTION
					"Numero de leds con error."
				::= { masterErrores 9 }

			masterModulos OBJECT-TYPE
				SYNTAX Integer32
				ACCESS read-only
				STATUS current
				DESCRIPTION
					"Numero de filas de modulos con error."
				::= { masterErrores 10 }

			masterResetSW OBJECT-TYPE
				SYNTAX Integer32
				ACCESS read-write
				STATUS current
				DESCRIPTION
					"Reset Software (1 = SI)."
				::= { masterErrores 11 }

			masterResetSWNA OBJECT-TYPE
				SYNTAX Integer32
				ACCESS read-write
				STATUS current
				DESCRIPTION
					"Reset Software Sin Apagar (1 = SI)."
				::= { masterErrores 12 }

			masterResetHW OBJECT-TYPE
				SYNTAX Integer32
				ACCESS read-write
				STATUS current
				DESCRIPTION
					"Reset Hardware (1 = SI)."
				::= { masterErrores 13 }

			masterTestRGB OBJECT-TYPE
				SYNTAX Integer32
				ACCESS read-write
				STATUS current
				DESCRIPTION
					"Test RGB (1 = SI)."
				::= { masterErrores 14 }

			masterTestAudio OBJECT-TYPE
				SYNTAX Integer32
				ACCESS read-write
				STATUS current
				DESCRIPTION
					"Test Audio (1 = SI)."
				::= { masterErrores 15 }

			
		masterNotificaciones OBJECT IDENTIFIER ::= { master 2 }


			masterErrorUsbErrors NOTIFICATION-TYPE
				STATUS current
				DESCRIPTION
					"Error Usb."
				::= { masterNotificaciones 2 } 
		
			masterPuertaAbierta NOTIFICATION-TYPE
				STATUS current
				DESCRIPTION
					"Puerta abierta."
				::= { masterNotificaciones 3 } 
		
			masterTemperaturaExcedida NOTIFICATION-TYPE
				STATUS current
				DESCRIPTION
					"Temperatura excedida."
				::= { masterNotificaciones 4 }
		
			masterErrorVentiladores NOTIFICATION-TYPE
				STATUS current
				DESCRIPTION
					"Fallo en ventiladores."
				::= { masterNotificaciones 5 }
		
			masterErrorLeds NOTIFICATION-TYPE
				STATUS current
				DESCRIPTION
					"Leds con error."
				::= { masterNotificaciones 6 }  
		
			masterErrorModulos NOTIFICATION-TYPE
				STATUS current
				DESCRIPTION
					"Modulos Led con error."
				::= { masterNotificaciones 7 }  
		
			masterImpacto NOTIFICATION-TYPE
				STATUS current
				DESCRIPTION
					"Impacto (en Gs)."
				::= { masterNotificaciones 8 }  

			masterErrorFotocelula NOTIFICATION-TYPE
				STATUS current
				DESCRIPTION
					"Fotocelula con error."
				::= { masterNotificaciones 9 }  

	
trapParameters OBJECT IDENTIFIER ::= { textel-Marimon 3 }

		
	trapIp OBJECT-TYPE
		SYNTAX OCTET STRING
		ACCESS read-write
		STATUS current
		DESCRIPTION
			"IP del administrador para envio de traps."
		::= { trapParameters 1 }

	trapPort OBJECT-TYPE
		SYNTAX OCTET STRING
		ACCESS read-write
		STATUS current
		DESCRIPTION
			"Puerto del administrador para envio de traps."
		::= { trapParameters 2 }


configService OBJECT IDENTIFIER ::= { textel-Marimon 4 }


	initialConfig OBJECT IDENTIFIER ::= { configService 1 }
		
		idPanel OBJECT-TYPE
			SYNTAX Integer32
			ACCESS read-only
			STATUS current
			DESCRIPTION
				"identificador interno del operador
				 (0 - 9999999999)"
			::= { initialConfig 1 }

		modo OBJECT-TYPE
			SYNTAX Integer32
			ACCESS read-only
			STATUS current
			DESCRIPTION
				"modo en que trabaja el panel (
				 0 = deshabilitado,
				 1 = normal
				 2 = sin estimaciones
				 3 = mantenimiento)"
			::= { initialConfig 2 }

		modoMultiidioma OBJECT-TYPE
			SYNTAX Integer32
			ACCESS read-only
			STATUS current
			DESCRIPTION
				"multiidioma habilitado (
				 0 = no
				 1 = si)"
			::= { initialConfig 3 }

		idiomas OBJECT-TYPE
			SYNTAX OCTET STRING
			ACCESS read-only
			STATUS current
			DESCRIPTION
				"array de identificadores de idiomas,
				 uno como minimo (ES)"
			::= { initialConfig 4 }

	consultaInfoConfig OBJECT IDENTIFIER ::= { configService 2 }
		

		paradas OBJECT-TYPE
			SYNTAX OCTET STRING
			ACCESS read-only
			STATUS current
			DESCRIPTION
				"listado paradas para el ambito del panel."
			::= { consultaInfoConfig 1 }

		urlSm OBJECT-TYPE
			SYNTAX OCTET STRING
			ACCESS read-only
			STATUS current
			DESCRIPTION
				"Endpoint del servicio StopMonitoring."
			::= { consultaInfoConfig 2 }

		urlSx OBJECT-TYPE
			SYNTAX OCTET STRING
			ACCESS read-only
			STATUS current
			DESCRIPTION
				"Endpoint del servicio SituationExchange."
			::= { consultaInfoConfig 3 }

		refrescoSm OBJECT-TYPE
			SYNTAX Integer32
			ACCESS read-only
			STATUS current
			DESCRIPTION
				"Tiempo entre llamadas SM
				 5 - 600 (seg)"
			::= { consultaInfoConfig 4 }

		refrescoSx OBJECT-TYPE
			SYNTAX Integer32
			ACCESS read-only
			STATUS current
			DESCRIPTION
				"Tiempo entre llamadas SX
				 5 - 600 (seg)"
			::= { consultaInfoConfig 5 }

		alternanciaMultiidioma OBJECT-TYPE
			SYNTAX Integer32
			ACCESS read-only
			STATUS current
			DESCRIPTION
				"Modo de alternancia (
				 0 = alterno M1-M2-X1-X2
				 1 = seguido M1-X1-M2-X2)"
			::= { consultaInfoConfig 6 }

		duracionEstimaciones OBJECT-TYPE
			SYNTAX Integer32
			ACCESS read-only
			STATUS current
			DESCRIPTION
				"duraci—n pantalla estimaciones
				 5 - 300 (seg)"
			::= { consultaInfoConfig 7 }

		duracionAvisos OBJECT-TYPE
			SYNTAX Integer32
			ACCESS read-only
			STATUS current
			DESCRIPTION
				"duraci—n pantalla avisos
				 5 - 300 (seg)"
			::= { consultaInfoConfig 8 }

		velocidadScrollH OBJECT-TYPE
			SYNTAX Integer32
			ACCESS read-only
			STATUS current
			DESCRIPTION
				"velocidad texto horizontal (0 - 100)
				 50 = standard"
			::= { consultaInfoConfig 9 }

		velocidadScrollV OBJECT-TYPE
			SYNTAX Integer32
			ACCESS read-only
			STATUS current
			DESCRIPTION
				"velocidad texto vertical (0 - 100)
				 50 = standard"
			::= { consultaInfoConfig 10 }

		colorEstimaciones OBJECT-TYPE
			SYNTAX OCTET STRING
			ACCESS read-only
			STATUS current
			DESCRIPTION
				"color hexadecimal pantalla estimaciones
				 (000000 - FFFFFF)"
			::= { consultaInfoConfig 11 }

		colorTituloAviso OBJECT-TYPE
			SYNTAX OCTET STRING
			ACCESS read-only
			STATUS current
			DESCRIPTION
				"color hexadecimal titulo pantalla avisos
				 (000000 - FFFFFF)"
			::= { consultaInfoConfig 12 }

		colorTextoAviso OBJECT-TYPE
			SYNTAX OCTET STRING
			ACCESS read-only
			STATUS current
			DESCRIPTION
				"color hexadecimal texto pantalla avisos
				 (000000 - FFFFFF)"
			::= { consultaInfoConfig 13 }

		tiempoLlegadaProxima OBJECT-TYPE
			SYNTAX Integer32
			ACCESS read-only
			STATUS current
			DESCRIPTION
				"tramo en que se muestra textoProx
				 5 - 300 (seg)"
			::= { consultaInfoConfig 14 }

		textoProx OBJECT-TYPE
			SYNTAX OCTET STRING
			ACCESS read-only
			STATUS current
			DESCRIPTION
				"array textoProx en diferentes idiomas
				 (c—digo idioma / texto)"
			::= { consultaInfoConfig 15 }

		tiempoLlegadaMaximo OBJECT-TYPE
			SYNTAX Integer32
			ACCESS read-only
			STATUS current
			DESCRIPTION
				"tramo durante el que se muestra estimacion
				 1 - 1440 (minutos)"
			::= { consultaInfoConfig 16 }

		tiempoMaximoError OBJECT-TYPE
			SYNTAX Integer32
			ACCESS read-only
			STATUS current
			DESCRIPTION
				"periodo sin estimaciones validas
				 para mostrar defaultText
				 1 - 60 (minutos)"
			::= { consultaInfoConfig 17 }

		textoDefectoError OBJECT-TYPE
			SYNTAX OCTET STRING
			ACCESS read-only
			STATUS current
			DESCRIPTION
				"texto a mostrar cuando Error"
			::= { consultaInfoConfig 18 }

		textoMantenimiento OBJECT-TYPE
			SYNTAX OCTET STRING
			ACCESS read-only
			STATUS current
			DESCRIPTION
				"texto a mostrar cuando Mantenimiento"
			::= { consultaInfoConfig 19 }

		fechaHoraDefecto OBJECT-TYPE
			SYNTAX Integer32
			ACCESS read-only
			STATUS current
			DESCRIPTION
				"a–adir fechaHora a defaultText y mantenimiento"
			::= { consultaInfoConfig 20 }

		curvaBrillo OBJECT-TYPE
			SYNTAX OCTET STRING
			ACCESS read-only
			STATUS current
			DESCRIPTION
				"array franjasBrillo
				 (hora HH:MM / porcentaje brillo 0 - 100)"
			::= { consultaInfoConfig 21 }

END
